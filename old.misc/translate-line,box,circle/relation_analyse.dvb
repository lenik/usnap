Attribute VB_Name = "Module1"
Option Explicit

Sub toSrc()
    Dim s As Single, sNear As Single, sNearI As Integer
End Sub

Sub showName()
    ThisDrawing.SelectionSets.Count
End Sub

Public Sub HelloWorld()
    'ThisDrawing.Application.Documents.Add
    Dim insPoint(0 To 2) As Double
    Dim textHeight As Double
    Dim textStr As String
    Dim textObj As AcadText
    
    insPoint(0) = 2
    insPoint(1) = 4
    insPoint(2) = 0
    
    textHeight = 1
    textStr = "Hello, world!"
    'Set textObj =
    ThisDrawing.PaperSpace.AddText textStr, insPoint, textHeight
End Sub
